string dim_cmd,cmd="ripup GND;change drill 13;change thermals off;";
int s=254*32;
int first=1;

board(B) {
  B.signals(S) {
    if(S.name=="GND") {
      S.vias(V) {
        sprintf(cmd,"%s\nvia 'GND' Round (%d %d);",cmd,V.x/s,V.y/s);
      }
    }
  }
  B.wires(W) {
    if(W.layer==20) {
      if(first) {
        sprintf(dim_cmd,"%spolygon 'GND' 6 (%d %d) ",dim_cmd,W.x1/s,W.y1/s);
        first=0;
      }
      if(W.curve!=0) {
        sprintf(dim_cmd,"%s %f (%d %d)",dim_cmd,W.curve,W.x2/s,W.y2/s);
      } else {
        sprintf(dim_cmd,"%s (%d %d)",dim_cmd,W.x2/s,W.y2/s);
      }
    }
  }
} 

sprintf(cmd,"%s\nchange layer 1;\n%s;\nchange layer 16;\n%s;\n",cmd,dim_cmd,dim_cmd);
dlgMessageBox(cmd);
exit(cmd);
